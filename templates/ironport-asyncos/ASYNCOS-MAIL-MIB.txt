ASYNCOS-MAIL-MIB DEFINITIONS ::= BEGIN

-- Enterprise MIB for IronPort Systems Mail Gateway Appliances
-- Compatible with SNMP Version 2.

IMPORTS
    MODULE-IDENTITY, Counter32, Gauge32 FROM SNMPv2-SMI
    DisplayString, TruthValue FROM SNMPv2-TC
    TRAP-TYPE FROM RFC-1215
    asyncOSMail FROM  IRONPORT-SMI;

asyncOSMailObjects MODULE-IDENTITY
    LAST-UPDATED "200605110000Z"
    ORGANIZATION "IronPort Systems"
    CONTACT-INFO "Postal: 950 Elm Avenue
                  San Bruno, CA 94066
     
                  Email:  customersupport@ironport.com"
    DESCRIPTION
                  "Enterprise MIB for IronPort Systems Mail Gateway Appliances"
    REVISION      "200605110000Z"
                   DESCRIPTION
                   "Minor Corrections to Comments."
                  ::= { asyncOSMail 1 }


-- asyncOSMailObjects OBJECT IDENTIFIER ::= { asyncOSMail 1 }
asyncOSMailNotifications OBJECT IDENTIFIER ::= { asyncOSMail 2 }

perCentMemoryUtilization OBJECT-TYPE
    SYNTAX INTEGER(0..100)
    ACCESS read-only
    STATUS mandatory
    DESCRIPTION
        "Percent memory utilization."
    ::= {asyncOSMailObjects 1}

perCentCPUUtilization OBJECT-TYPE
    SYNTAX INTEGER(0..100)
    ACCESS read-only
    STATUS mandatory
    DESCRIPTION
        "Percent CPU utilization."
    ::= {asyncOSMailObjects 2}

perCentDiskIOUtilization OBJECT-TYPE
    SYNTAX INTEGER(0..100)
    ACCESS read-only
    STATUS mandatory
    DESCRIPTION
        "Percent disk I/O utilization."
    ::= {asyncOSMailObjects 3}

perCentQueueUtilization OBJECT-TYPE
    SYNTAX INTEGER(0..100)
    ACCESS read-only
    STATUS mandatory
    DESCRIPTION
        "Percent of total queue capacity used."
    ::= {asyncOSMailObjects 4}

queueAvailabilityStatus OBJECT-TYPE
    SYNTAX INTEGER {
        queueSpaceAvailable(1),
        queueSpaceShortage(2),
        queueFull(3)
        }
    ACCESS read-only
    STATUS mandatory
    DESCRIPTION
        "Queue space status: enough space, queue near full or queue full."
    ::= { asyncOSMailObjects 5}

resourceConservationReason OBJECT-TYPE
    SYNTAX INTEGER {
        noResourceConservation(1),
        memoryShortage(2),
        queueSpaceShortage(3),
        queueFull(4)
        }
    ACCESS read-only
    STATUS mandatory
    DESCRIPTION
        "Reason system is in Resource Conservation Mode."
    ::= { asyncOSMailObjects 6}

memoryAvailabilityStatus OBJECT-TYPE
    SYNTAX INTEGER {
        memoryAvailable(1),
        memoryShortage(2),
        memoryFull(3)
        }
    ACCESS read-only
    STATUS mandatory
    DESCRIPTION
        "Mail Transfer process's memory availability status."
    ::= { asyncOSMailObjects 7}

powerSupplyTable OBJECT-TYPE
    SYNTAX SEQUENCE OF PowerSupplyEntry
    ACCESS not-accessible
    STATUS mandatory
    DESCRIPTION
        "A list of power supply entries."
    ::= {asyncOSMailObjects 8}

powerSupplyEntry OBJECT-TYPE
    SYNTAX PowerSupplyEntry
    ACCESS not-accessible
    STATUS mandatory
    DESCRIPTION
        "Entry containing status of a power supply."
    INDEX { powerSupplyIndex }
    ::= { powerSupplyTable 1 }

PowerSupplyEntry ::= SEQUENCE {
    powerSupplyIndex INTEGER,
    powerSupplyStatus INTEGER,
    powerSupplyRedundancy INTEGER,
    powerSupplyName DisplayString
    }

powerSupplyIndex OBJECT-TYPE
    SYNTAX INTEGER(1..8)
    ACCESS not-accessible
    STATUS mandatory
    DESCRIPTION
        "Module index into powerSupplyTable."
    ::= { powerSupplyEntry 1 }

powerSupplyStatus OBJECT-TYPE
    SYNTAX INTEGER {
        powerSupplyNotInstalled(1),
        powerSupplyHealthy(2),
        powerSupplyNoAC(3),
        powerSupplyFaulty(4)
        }
    ACCESS read-only
    STATUS mandatory
    DESCRIPTION
        "The overall status of power supply."
    ::= { powerSupplyEntry 2 }

powerSupplyRedundancy OBJECT-TYPE
    SYNTAX INTEGER {
        powerSupplyRedundancyOK(1),
        powerSupplyRedundancyLost(2)
        }
    ACCESS read-only
    STATUS mandatory
    DESCRIPTION
        "The status of power supply redundancy."
    ::= { powerSupplyEntry 3 }

powerSupplyName OBJECT-TYPE
    SYNTAX DisplayString
    ACCESS read-only
    STATUS mandatory
    DESCRIPTION
        "Name of power supply.  E.g., PS 1."
    ::= { powerSupplyEntry 4 }

temperatureTable OBJECT-TYPE
    SYNTAX SEQUENCE OF TemperatureEntry
    ACCESS not-accessible
    STATUS mandatory
    DESCRIPTION
        "A set of temperature entries."
    ::= {asyncOSMailObjects 9}

temperatureEntry OBJECT-TYPE
    SYNTAX TemperatureEntry
    ACCESS not-accessible
    STATUS mandatory
    DESCRIPTION
        "Entry containing temperature in Celsius and name of sensor."
    INDEX { temperatureIndex }
    ::= { temperatureTable 1 }

TemperatureEntry ::= SEQUENCE {
    temperatureIndex INTEGER,
    degreesCelsius INTEGER,
    temperatureName DisplayString
    }

temperatureIndex OBJECT-TYPE
    SYNTAX INTEGER(1..8)
    ACCESS not-accessible
    STATUS mandatory
    DESCRIPTION
        "Index into temperatureTable."
    ::= { temperatureEntry 1 }

degreesCelsius OBJECT-TYPE
    SYNTAX INTEGER
    ACCESS read-only
    STATUS mandatory
    DESCRIPTION
        "Temperature in degrees Celsius."
    ::= { temperatureEntry 2 }

temperatureName OBJECT-TYPE
    SYNTAX DisplayString
    ACCESS read-only
    STATUS mandatory
    DESCRIPTION
        "Descriptive name of measurement.  E.g. Ambient Temperature."
    ::= { temperatureEntry 3 }

fanTable OBJECT-TYPE
    SYNTAX SEQUENCE OF FanEntry
    ACCESS not-accessible
    STATUS mandatory
    DESCRIPTION
        "A set of fan entries."
    ::= {asyncOSMailObjects 10}

fanEntry OBJECT-TYPE
    SYNTAX FanEntry
    ACCESS not-accessible
    STATUS mandatory
    DESCRIPTION
        "Entry containing speed of fan in RPMs."
    INDEX { fanIndex }
    ::= { fanTable 1 }

FanEntry ::= SEQUENCE {
    fanIndex INTEGER,
    fanRPMs Gauge32,
    fanName DisplayString
    }

fanIndex OBJECT-TYPE
    SYNTAX INTEGER(1..8)
    ACCESS not-accessible
    STATUS mandatory
    DESCRIPTION
        "Index into fanTable."
    ::= { fanEntry 1 }

fanRPMs OBJECT-TYPE
    SYNTAX Gauge32
    ACCESS read-only
    STATUS mandatory
    DESCRIPTION
        "Fan speed in RPMs."
    ::= { fanEntry 2 }

fanName OBJECT-TYPE
    SYNTAX DisplayString
    ACCESS read-only
    STATUS mandatory
    DESCRIPTION
        "Name of Fan.  E.g., FAN 1."
    ::= { fanEntry 3 }

workQueueMessages OBJECT-TYPE
    SYNTAX Gauge32
    ACCESS read-only
    STATUS mandatory
    DESCRIPTION
        "Number of messages in the work queue."
    ::= {asyncOSMailObjects 11}

keyExpirationTable OBJECT-TYPE
    SYNTAX SEQUENCE OF KeyExpirationEntry
    ACCESS not-accessible
    STATUS mandatory
    DESCRIPTION
        "A set of key expiration entries."
    ::= {asyncOSMailObjects 12}

keyExpirationEntry OBJECT-TYPE
    SYNTAX KeyExpirationEntry
    ACCESS not-accessible
    STATUS mandatory
    DESCRIPTION
        "Entry containing a key's expiration status."
    INDEX { keyExpirationIndex }
    ::= { keyExpirationTable 1 }

KeyExpirationEntry ::= SEQUENCE {
    keyExpirationIndex INTEGER,
    keyDescription DisplayString,
    keyIsPerpetual TruthValue,
    keySecondsUntilExpire Gauge32
    }

keyExpirationIndex OBJECT-TYPE
    SYNTAX INTEGER(1..1024)
    ACCESS not-accessible
    STATUS mandatory
    DESCRIPTION
        "Index into key Expiration Table."
    ::= { keyExpirationEntry 1 }

keyDescription OBJECT-TYPE
    SYNTAX DisplayString
    ACCESS read-only
    STATUS mandatory
    DESCRIPTION
        "Description of key."
    ::= { keyExpirationEntry 2 }

keyIsPerpetual OBJECT-TYPE
    SYNTAX TruthValue
    ACCESS read-only
    STATUS mandatory
    DESCRIPTION
        "True if key is perpetual"
    ::= { keyExpirationEntry 3 }

keySecondsUntilExpire OBJECT-TYPE
    SYNTAX Gauge32
    ACCESS read-only
    STATUS mandatory
    DESCRIPTION
        "Seconds until key expires."
    ::= { keyExpirationEntry 4 }

updateTable OBJECT-TYPE
    SYNTAX SEQUENCE OF UpdateEntry
    ACCESS not-accessible
    STATUS mandatory
    DESCRIPTION
        "A set of update entries."
    ::= {asyncOSMailObjects 13}

updateEntry OBJECT-TYPE
    SYNTAX UpdateEntry
    ACCESS not-accessible
    STATUS mandatory
    DESCRIPTION
        "Entry containing updates and update failures."
    INDEX { updateIndex }
    ::= { updateTable 1 }

UpdateEntry ::= SEQUENCE {
    updateIndex INTEGER,
    updateServiceName DisplayString,
    updates Counter32,
    updateFailures Counter32
    }

updateIndex OBJECT-TYPE
    SYNTAX INTEGER(1..1024)
    ACCESS not-accessible
    STATUS mandatory
    DESCRIPTION
        "Index into updateTable."
    ::= { updateEntry 1 }

updateServiceName OBJECT-TYPE
    SYNTAX DisplayString
    ACCESS read-only
    STATUS mandatory
    DESCRIPTION
        "Name of service for which update has been done."
    ::= { updateEntry 2 }

updates OBJECT-TYPE
    SYNTAX Counter32
    ACCESS read-only
    STATUS mandatory
    DESCRIPTION
        "Number of updates."
    ::= { updateEntry 3 }

updateFailures OBJECT-TYPE
    SYNTAX Counter32
    ACCESS read-only
    STATUS mandatory
    DESCRIPTION
        "Number of update failures."
    ::= { updateEntry 4 }

oldestMessageAge OBJECT-TYPE
    SYNTAX Gauge32
    ACCESS read-only
    STATUS mandatory
    DESCRIPTION
        "The number of seconds the oldest message has been in queue"
    ::= {asyncOSMailObjects 14}

outstandingDNSRequests OBJECT-TYPE
    SYNTAX Gauge32
    ACCESS read-only
    STATUS mandatory
    DESCRIPTION
        "Number of DNS requests that have been sent but for which no
         reply has been received."
    ::= {asyncOSMailObjects 15}

pendingDNSRequests OBJECT-TYPE
    SYNTAX Gauge32
    ACCESS read-only
    STATUS mandatory
    DESCRIPTION
        "Number of DNS requests waiting to be sent."
    ::= {asyncOSMailObjects 16}

raidEvents OBJECT-TYPE
    SYNTAX Counter32
    ACCESS read-only
    STATUS mandatory
    DESCRIPTION
        "Number of RAID events."
    ::= {asyncOSMailObjects 17}

raidTable                 OBJECT-TYPE
    SYNTAX SEQUENCE OF RAIDEntry
    ACCESS not-accessible
    STATUS mandatory
    DESCRIPTION
        "A set of RAID entries"
    ::= {asyncOSMailObjects 18}

raidEntry OBJECT-TYPE
    SYNTAX RAIDEntry
    ACCESS not-accessible
    STATUS mandatory
    DESCRIPTION
        "Entry containing status of a RAID drive."
    INDEX { raidIndex }
    ::= { raidTable 1 }

RAIDEntry ::= SEQUENCE {
    raidIndex INTEGER,
    raidStatus INTEGER,
    raidID DisplayString,
    raidLastError DisplayString
    }

raidIndex OBJECT-TYPE
    SYNTAX INTEGER(1..8)
    ACCESS not-accessible
    STATUS mandatory
    DESCRIPTION
        "Index into raidTable."
    ::= { raidEntry 1 }

raidStatus OBJECT-TYPE
    SYNTAX INTEGER {
        driveHealthy(1),
        driveFailure(2),
        driveRebuild(3)
        }
    ACCESS read-only
    STATUS mandatory
    DESCRIPTION
        "Status reported by RAID controller."
    ::= { raidEntry 2 }

raidID OBJECT-TYPE
    SYNTAX DisplayString
    ACCESS read-only
    STATUS mandatory
    DESCRIPTION
        "Name of RAID component.  E.g.: RAID 1, DISK 2."
    ::= { raidEntry 3 }

raidLastError OBJECT-TYPE
    SYNTAX DisplayString
    ACCESS read-only
    STATUS mandatory
    DESCRIPTION
        "Last RAID Error Message."
    ::= { raidEntry 4 }

openFilesOrSockets OBJECT-TYPE
    SYNTAX Gauge32
    ACCESS read-only
    STATUS mandatory
    DESCRIPTION
        "Number of open files or sockets."
    ::= {asyncOSMailObjects 19}

mailTransferThreads OBJECT-TYPE
    SYNTAX Gauge32
    ACCESS read-only
    STATUS mandatory
    DESCRIPTION
        "Number of threads that perform some task related to
         transferring mail."
    ::= {asyncOSMailObjects 20}

 

--
--  Notifications
--

resourceConservationMode TRAP-TYPE
    ENTERPRISE asyncOSMailNotifications
    VARIABLES { resourceConservationReason }
    DESCRIPTION
        "Memory or queue utilization caused system to enter resource
         conservation mode."
    ::= 1

powerSupplyStatusChange TRAP-TYPE
    ENTERPRISE asyncOSMailNotifications
    VARIABLES {
        powerSupplyStatus }
    DESCRIPTION
        "Sent when power supply status changes."
    ::= 2

highTemperature TRAP-TYPE
    ENTERPRISE asyncOSMailNotifications
    VARIABLES {
        temperatureName }
    DESCRIPTION
        "Temperature has exceeded a recoverable failure threshold."
    ::= 3

fanFailure TRAP-TYPE
    ENTERPRISE asyncOSMailNotifications
    VARIABLES {
        fanName }
    DESCRIPTION
        "Speed of fan fanName has gone to zero."
    ::= 4

keyExpiration TRAP-TYPE
    ENTERPRISE asyncOSMailNotifications
    VARIABLES {
        keyDescription }
    DESCRIPTION
        "Key will expire."
    ::= 5

updateFailure TRAP-TYPE
    ENTERPRISE asyncOSMailNotifications
    VARIABLES {
        updateServiceName }
    DESCRIPTION
        "Update failure (spam rules, virus patterns, outbreak updates, etc.)"
    ::= 6

raidStatusChange TRAP-TYPE
    ENTERPRISE asyncOSMailNotifications
    VARIABLES {
        raidID }
    DESCRIPTION
        "Drive with ID: RAIDID has changed status."
    ::= 7

END
****************File contents above************************

IRONPORT-SMI.txt

**********File contents Below*****************************

ASYNCOS-MAIL-MIB DEFINITIONS ::= BEGIN

-- Enterprise MIB for IronPort Systems Mail Gateway Appliances
-- Compatible with SNMP Version 2.

IMPORTS
    MODULE-IDENTITY, Counter32, Gauge32 FROM SNMPv2-SMI
    DisplayString, TruthValue FROM SNMPv2-TC
    TRAP-TYPE FROM RFC-1215
    asyncOSMail FROM  IRONPORT-SMI;

asyncOSMailObjects MODULE-IDENTITY
    LAST-UPDATED "200605110000Z"
    ORGANIZATION "IronPort Systems"
    CONTACT-INFO "Postal: 950 Elm Avenue
                  San Bruno, CA 94066
     
                  Email:  customersupport@ironport.com"
    DESCRIPTION
                  "Enterprise MIB for IronPort Systems Mail Gateway Appliances"
    REVISION      "200605110000Z"
                   DESCRIPTION
                   "Minor Corrections to Comments."
                  ::= { asyncOSMail 1 }


-- asyncOSMailObjects OBJECT IDENTIFIER ::= { asyncOSMail 1 }
asyncOSMailNotifications OBJECT IDENTIFIER ::= { asyncOSMail 2 }

perCentMemoryUtilization OBJECT-TYPE
    SYNTAX INTEGER(0..100)
    ACCESS read-only
    STATUS mandatory
    DESCRIPTION
        "Percent memory utilization."
    ::= {asyncOSMailObjects 1}

perCentCPUUtilization OBJECT-TYPE
    SYNTAX INTEGER(0..100)
    ACCESS read-only
    STATUS mandatory
    DESCRIPTION
        "Percent CPU utilization."
    ::= {asyncOSMailObjects 2}

perCentDiskIOUtilization OBJECT-TYPE
    SYNTAX INTEGER(0..100)
    ACCESS read-only
    STATUS mandatory
    DESCRIPTION
        "Percent disk I/O utilization."
    ::= {asyncOSMailObjects 3}

perCentQueueUtilization OBJECT-TYPE
    SYNTAX INTEGER(0..100)
    ACCESS read-only
    STATUS mandatory
    DESCRIPTION
        "Percent of total queue capacity used."
    ::= {asyncOSMailObjects 4}

queueAvailabilityStatus OBJECT-TYPE
    SYNTAX INTEGER {
        queueSpaceAvailable(1),
        queueSpaceShortage(2),
        queueFull(3)
        }
    ACCESS read-only
    STATUS mandatory
    DESCRIPTION
        "Queue space status: enough space, queue near full or queue full."
    ::= { asyncOSMailObjects 5}

resourceConservationReason OBJECT-TYPE
    SYNTAX INTEGER {
        noResourceConservation(1),
        memoryShortage(2),
        queueSpaceShortage(3),
        queueFull(4)
        }
    ACCESS read-only
    STATUS mandatory
    DESCRIPTION
        "Reason system is in Resource Conservation Mode."
    ::= { asyncOSMailObjects 6}

memoryAvailabilityStatus OBJECT-TYPE
    SYNTAX INTEGER {
        memoryAvailable(1),
        memoryShortage(2),
        memoryFull(3)
        }
    ACCESS read-only
    STATUS mandatory
    DESCRIPTION
        "Mail Transfer process's memory availability status."
    ::= { asyncOSMailObjects 7}

powerSupplyTable OBJECT-TYPE
    SYNTAX SEQUENCE OF PowerSupplyEntry
    ACCESS not-accessible
    STATUS mandatory
    DESCRIPTION
        "A list of power supply entries."
    ::= {asyncOSMailObjects 8}

powerSupplyEntry OBJECT-TYPE
    SYNTAX PowerSupplyEntry
    ACCESS not-accessible
    STATUS mandatory
    DESCRIPTION
        "Entry containing status of a power supply."
    INDEX { powerSupplyIndex }
    ::= { powerSupplyTable 1 }

PowerSupplyEntry ::= SEQUENCE {
    powerSupplyIndex INTEGER,
    powerSupplyStatus INTEGER,
    powerSupplyRedundancy INTEGER,
    powerSupplyName DisplayString
    }

powerSupplyIndex OBJECT-TYPE
    SYNTAX INTEGER(1..8)
    ACCESS not-accessible
    STATUS mandatory
    DESCRIPTION
        "Module index into powerSupplyTable."
    ::= { powerSupplyEntry 1 }

powerSupplyStatus OBJECT-TYPE
    SYNTAX INTEGER {
        powerSupplyNotInstalled(1),
        powerSupplyHealthy(2),
        powerSupplyNoAC(3),
        powerSupplyFaulty(4)
        }
    ACCESS read-only
    STATUS mandatory
    DESCRIPTION
        "The overall status of power supply."
    ::= { powerSupplyEntry 2 }

powerSupplyRedundancy OBJECT-TYPE
    SYNTAX INTEGER {
        powerSupplyRedundancyOK(1),
        powerSupplyRedundancyLost(2)
        }
    ACCESS read-only
    STATUS mandatory
    DESCRIPTION
        "The status of power supply redundancy."
    ::= { powerSupplyEntry 3 }

powerSupplyName OBJECT-TYPE
    SYNTAX DisplayString
    ACCESS read-only
    STATUS mandatory
    DESCRIPTION
        "Name of power supply.  E.g., PS 1."
    ::= { powerSupplyEntry 4 }

temperatureTable OBJECT-TYPE
    SYNTAX SEQUENCE OF TemperatureEntry
    ACCESS not-accessible
    STATUS mandatory
    DESCRIPTION
        "A set of temperature entries."
    ::= {asyncOSMailObjects 9}

temperatureEntry OBJECT-TYPE
    SYNTAX TemperatureEntry
    ACCESS not-accessible
    STATUS mandatory
    DESCRIPTION
        "Entry containing temperature in Celsius and name of sensor."
    INDEX { temperatureIndex }
    ::= { temperatureTable 1 }

TemperatureEntry ::= SEQUENCE {
    temperatureIndex INTEGER,
    degreesCelsius INTEGER,
    temperatureName DisplayString
    }

temperatureIndex OBJECT-TYPE
    SYNTAX INTEGER(1..8)
    ACCESS not-accessible
    STATUS mandatory
    DESCRIPTION
        "Index into temperatureTable."
    ::= { temperatureEntry 1 }

degreesCelsius OBJECT-TYPE
    SYNTAX INTEGER
    ACCESS read-only
    STATUS mandatory
    DESCRIPTION
        "Temperature in degrees Celsius."
    ::= { temperatureEntry 2 }

temperatureName OBJECT-TYPE
    SYNTAX DisplayString
    ACCESS read-only
    STATUS mandatory
    DESCRIPTION
        "Descriptive name of measurement.  E.g. Ambient Temperature."
    ::= { temperatureEntry 3 }

fanTable OBJECT-TYPE
    SYNTAX SEQUENCE OF FanEntry
    ACCESS not-accessible
    STATUS mandatory
    DESCRIPTION
        "A set of fan entries."
    ::= {asyncOSMailObjects 10}

fanEntry OBJECT-TYPE
    SYNTAX FanEntry
    ACCESS not-accessible
    STATUS mandatory
    DESCRIPTION
        "Entry containing speed of fan in RPMs."
    INDEX { fanIndex }
    ::= { fanTable 1 }

FanEntry ::= SEQUENCE {
    fanIndex INTEGER,
    fanRPMs Gauge32,
    fanName DisplayString
    }

fanIndex OBJECT-TYPE
    SYNTAX INTEGER(1..8)
    ACCESS not-accessible
    STATUS mandatory
    DESCRIPTION
        "Index into fanTable."
    ::= { fanEntry 1 }

fanRPMs OBJECT-TYPE
    SYNTAX Gauge32
    ACCESS read-only
    STATUS mandatory
    DESCRIPTION
        "Fan speed in RPMs."
    ::= { fanEntry 2 }

fanName OBJECT-TYPE
    SYNTAX DisplayString
    ACCESS read-only
    STATUS mandatory
    DESCRIPTION
        "Name of Fan.  E.g., FAN 1."
    ::= { fanEntry 3 }

workQueueMessages OBJECT-TYPE
    SYNTAX Gauge32
    ACCESS read-only
    STATUS mandatory
    DESCRIPTION
        "Number of messages in the work queue."
    ::= {asyncOSMailObjects 11}

keyExpirationTable OBJECT-TYPE
    SYNTAX SEQUENCE OF KeyExpirationEntry
    ACCESS not-accessible
    STATUS mandatory
    DESCRIPTION
        "A set of key expiration entries."
    ::= {asyncOSMailObjects 12}

keyExpirationEntry OBJECT-TYPE
    SYNTAX KeyExpirationEntry
    ACCESS not-accessible
    STATUS mandatory
    DESCRIPTION
        "Entry containing a key's expiration status."
    INDEX { keyExpirationIndex }
    ::= { keyExpirationTable 1 }

KeyExpirationEntry ::= SEQUENCE {
    keyExpirationIndex INTEGER,
    keyDescription DisplayString,
    keyIsPerpetual TruthValue,
    keySecondsUntilExpire Gauge32
    }

keyExpirationIndex OBJECT-TYPE
    SYNTAX INTEGER(1..1024)
    ACCESS not-accessible
    STATUS mandatory
    DESCRIPTION
        "Index into key Expiration Table."
    ::= { keyExpirationEntry 1 }

keyDescription OBJECT-TYPE
    SYNTAX DisplayString
    ACCESS read-only
    STATUS mandatory
    DESCRIPTION
        "Description of key."
    ::= { keyExpirationEntry 2 }

keyIsPerpetual OBJECT-TYPE
    SYNTAX TruthValue
    ACCESS read-only
    STATUS mandatory
    DESCRIPTION
        "True if key is perpetual"
    ::= { keyExpirationEntry 3 }

keySecondsUntilExpire OBJECT-TYPE
    SYNTAX Gauge32
    ACCESS read-only
    STATUS mandatory
    DESCRIPTION
        "Seconds until key expires."
    ::= { keyExpirationEntry 4 }

updateTable OBJECT-TYPE
    SYNTAX SEQUENCE OF UpdateEntry
    ACCESS not-accessible
    STATUS mandatory
    DESCRIPTION
        "A set of update entries."
    ::= {asyncOSMailObjects 13}

updateEntry OBJECT-TYPE
    SYNTAX UpdateEntry
    ACCESS not-accessible
    STATUS mandatory
    DESCRIPTION
        "Entry containing updates and update failures."
    INDEX { updateIndex }
    ::= { updateTable 1 }

UpdateEntry ::= SEQUENCE {
    updateIndex INTEGER,
    updateServiceName DisplayString,
    updates Counter32,
    updateFailures Counter32
    }

updateIndex OBJECT-TYPE
    SYNTAX INTEGER(1..1024)
    ACCESS not-accessible
    STATUS mandatory
    DESCRIPTION
        "Index into updateTable."
    ::= { updateEntry 1 }

updateServiceName OBJECT-TYPE
    SYNTAX DisplayString
    ACCESS read-only
    STATUS mandatory
    DESCRIPTION
        "Name of service for which update has been done."
    ::= { updateEntry 2 }

updates OBJECT-TYPE
    SYNTAX Counter32
    ACCESS read-only
    STATUS mandatory
    DESCRIPTION
        "Number of updates."
    ::= { updateEntry 3 }

updateFailures OBJECT-TYPE
    SYNTAX Counter32
    ACCESS read-only
    STATUS mandatory
    DESCRIPTION
        "Number of update failures."
    ::= { updateEntry 4 }

oldestMessageAge OBJECT-TYPE
    SYNTAX Gauge32
    ACCESS read-only
    STATUS mandatory
    DESCRIPTION
        "The number of seconds the oldest message has been in queue"
    ::= {asyncOSMailObjects 14}

outstandingDNSRequests OBJECT-TYPE
    SYNTAX Gauge32
    ACCESS read-only
    STATUS mandatory
    DESCRIPTION
        "Number of DNS requests that have been sent but for which no
         reply has been received."
    ::= {asyncOSMailObjects 15}

pendingDNSRequests OBJECT-TYPE
    SYNTAX Gauge32
    ACCESS read-only
    STATUS mandatory
    DESCRIPTION
        "Number of DNS requests waiting to be sent."
    ::= {asyncOSMailObjects 16}

raidEvents OBJECT-TYPE
    SYNTAX Counter32
    ACCESS read-only
    STATUS mandatory
    DESCRIPTION
        "Number of RAID events."
    ::= {asyncOSMailObjects 17}

raidTable                 OBJECT-TYPE
    SYNTAX SEQUENCE OF RAIDEntry
    ACCESS not-accessible
    STATUS mandatory
    DESCRIPTION
        "A set of RAID entries"
    ::= {asyncOSMailObjects 18}

raidEntry OBJECT-TYPE
    SYNTAX RAIDEntry
    ACCESS not-accessible
    STATUS mandatory
    DESCRIPTION
        "Entry containing status of a RAID drive."
    INDEX { raidIndex }
    ::= { raidTable 1 }

RAIDEntry ::= SEQUENCE {
    raidIndex INTEGER,
    raidStatus INTEGER,
    raidID DisplayString,
    raidLastError DisplayString
    }

raidIndex OBJECT-TYPE
    SYNTAX INTEGER(1..8)
    ACCESS not-accessible
    STATUS mandatory
    DESCRIPTION
        "Index into raidTable."
    ::= { raidEntry 1 }

raidStatus OBJECT-TYPE
    SYNTAX INTEGER {
        driveHealthy(1),
        driveFailure(2),
        driveRebuild(3)
        }
    ACCESS read-only
    STATUS mandatory
    DESCRIPTION
        "Status reported by RAID controller."
    ::= { raidEntry 2 }

raidID OBJECT-TYPE
    SYNTAX DisplayString
    ACCESS read-only
    STATUS mandatory
    DESCRIPTION
        "Name of RAID component.  E.g.: RAID 1, DISK 2."
    ::= { raidEntry 3 }

raidLastError OBJECT-TYPE
    SYNTAX DisplayString
    ACCESS read-only
    STATUS mandatory
    DESCRIPTION
        "Last RAID Error Message."
    ::= { raidEntry 4 }

openFilesOrSockets OBJECT-TYPE
    SYNTAX Gauge32
    ACCESS read-only
    STATUS mandatory
    DESCRIPTION
        "Number of open files or sockets."
    ::= {asyncOSMailObjects 19}

mailTransferThreads OBJECT-TYPE
    SYNTAX Gauge32
    ACCESS read-only
    STATUS mandatory
    DESCRIPTION
        "Number of threads that perform some task related to
         transferring mail."
    ::= {asyncOSMailObjects 20}

 

--
--  Notifications
--

resourceConservationMode TRAP-TYPE
    ENTERPRISE asyncOSMailNotifications
    VARIABLES { resourceConservationReason }
    DESCRIPTION
        "Memory or queue utilization caused system to enter resource
         conservation mode."
    ::= 1

powerSupplyStatusChange TRAP-TYPE
    ENTERPRISE asyncOSMailNotifications
    VARIABLES {
        powerSupplyStatus }
    DESCRIPTION
        "Sent when power supply status changes."
    ::= 2

highTemperature TRAP-TYPE
    ENTERPRISE asyncOSMailNotifications
    VARIABLES {
        temperatureName }
    DESCRIPTION
        "Temperature has exceeded a recoverable failure threshold."
    ::= 3

fanFailure TRAP-TYPE
    ENTERPRISE asyncOSMailNotifications
    VARIABLES {
        fanName }
    DESCRIPTION
        "Speed of fan fanName has gone to zero."
    ::= 4

keyExpiration TRAP-TYPE
    ENTERPRISE asyncOSMailNotifications
    VARIABLES {
        keyDescription }
    DESCRIPTION
        "Key will expire."
    ::= 5

updateFailure TRAP-TYPE
    ENTERPRISE asyncOSMailNotifications
    VARIABLES {
        updateServiceName }
    DESCRIPTION
        "Update failure (spam rules, virus patterns, outbreak updates, etc.)"
    ::= 6

raidStatusChange TRAP-TYPE
    ENTERPRISE asyncOSMailNotifications
    VARIABLES {
        raidID }
    DESCRIPTION
        "Drive with ID: RAIDID has changed status."
    ::= 7

END
